GenericCDR-Schema DEFINITIONS IMPLICIT TAGS ::=
BEGIN
GenericCallDataRecord ::= SEQUENCE {
 firstName [APPLICATION 1] IMPLICIT UTF8String,
 lastName [APPLICATION 2] IMPLICIT UTF8String,
 recordNumber [APPLICATION 3] IMPLICIT INTEGER,
 age [APPLICATION 4] IMPLICIT INTEGER,
 isVIP [APPLICATION 5] IMPLICIT BOOLEAN,
 city [APPLICATION 6] IMPLICIT UTF8String ,
 country [APPLICATION 7] IMPLICIT UTF8String ,
 callingNumber [APPLICATION 8] IMPLICIT UTF8String (SIZE(1..20)),
 calledNumber [APPLICATION 9] IMPLICIT UTF8String (SIZE(1..20)),
 zipCode [APPLICATION 10] IMPLICIT UTF8String ,
 longitude [APPLICATION 11] IMPLICIT UTF8String,
 latitude [APPLICATION 12] IMPLICIT UTF8String,
 startDate [APPLICATION 16] IMPLICIT  UTF8String,
 startTime [APPLICATION 18] IMPLICIT UTF8String,
 duration [APPLICATION 19] IMPLICIT INTEGER
}
END
