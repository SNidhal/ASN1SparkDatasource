GenericCDR-Schema DEFINITIONS IMPLICIT TAGS ::=
BEGIN
GenericCallDataRecord ::= SEQUENCE {
 recordNumber [APPLICATION 2] IMPLICIT INTEGER,
 callingNumber [APPLICATION 8] IMPLICIT UTF8String (SIZE(1..20)),
 calledNumber [APPLICATION 9] IMPLICIT UTF8String (SIZE(1..20)),
 startDate [APPLICATION 16] IMPLICIT  UTF8String (SIZE(8)),
 startTime [APPLICATION 18] IMPLICIT UTF8String (SIZE(6)),
 duration [APPLICATION 19] IMPLICIT INTEGER
}
END
